# Missile_Reqs

## RFP: Range (Functional)
The range will be 500 nm from its launch to impact

## RFP: Cruise Speed (Functional)
The missile must have a minimum cruise speed above Mach 3.

## RFP: Mark 41 VLS (Functional)
Missile must be able to launch from Mark 41 VLS, Launch weight is less than 5000 lbm

## RFP: Land Based Launch (HIMARS) (Functional)
The missile must be able to be launched from Mobile land-based launchers (ie, HIMRAS, MLRS). Launch weight < 2000 lbm.

## RFP: External Fighter (Functional)
Missile must launch form an external fighter hard point. Launch weight < 2000 lbm.

## RFP: Submarine (Functional)
Missile must launch from a submarine tube. Launch weight < 3500 lbm.

## RFP: Internal Fighter (Functional)
Must launch from a figher internal carriage. Launch weight < 2000 lbm.

## RFP: Dimensions (Functional)
Missile fits in a 15 x 15 x 144 in box.

## RFP: Warhead (Functional)
Missile will have capability to neutralize a single target

## RFP: Data Links (Functional)
Missile will have data link commands to include changes in-flight

## RFP: Safe Storage (Functional)
Missile should be capable of safe storage up to 10 years without maintenance.

## RFP: Production Run (Functional)
Initial production run will be 1200 missiles per year for 10 years w/ 100 for developmental testing

## RFP: Surge Production (Functional)
Production should be surged up to 72 missiles per week (3744 missiles per year) within 1 week.

## RFP: Maintain Surge Production (Functional)
Surge production should be sustained indefinetly at 72 units per week.

## RFP: Low-Level Ingress (Functional)
Missile must have a low-level ingress to its target, traveling <= 500 ft AGL for the last 10% of its mission.

## RFP: Air Launch (Functional)
Missile must be capable of air launch at Mach 0.8 at 30,000 ft.

## MIL-M-8856B: Factor Safety (Functional)
Factor of safety will be a minimum of 1.5 for in-flight, storage, and transportation.

## MIL-M-8856B: Faliure under Ultimate Mission Load (Functional)
The structure will not fail under the ultimate load condition outlined in the mission profile

## MIL-STD-1522A: Extreme Temp (Functional)
Materials will be constructed based on extreme temperature cases seen during the mission profile

## MIL-M-8856B: Heating Effects (Functional)
Missile design shall provide for the cummulative heating effect from internal and external heating

## MIL-M-8856B: Fatigue Life (Functional)
The fatigue life of the structure will equal or exceed the specified life

## SMC-S-006: Proof Pressure (Functional)
Missile shall sustain specified proof pressure without any detrimental deformation

## SMC-S-006: Minimum Proof Pressure (Functional)
Minimum proof pressure will be 1.1 time the maximum expected operating pressure

## SMC-S-006: Stiffness (Functional)
All components will have enough stiffness to handle deformation at limit load

## SMC-S-006: Loading with Cracks (Functional)
Components will handle loads even with existing crack

## SMC-S-006: Fracture Toughness (Functional)
Fracture toughness in materials must be at a minimum of 60% of the plain strain toughness

## SMC-S-006: Fabrication (Functional)
Fabrication of materials will be within acceptable variable ranges and perform reliably

## MIL-STD-1522A: Internal Pressure (Functional)
The system will maintain safe conditions for pressure level inside necessary for flight conditions outlined

## MIL-STD-1901A: Ignition System Protection (Functional)
For safe storage, the ignition system will not arm during exposure to electronic attacks(ie. EMR, ESD,EMP)

## RTCA-DO-178: Software (Functional)
Missile software will comply to military software guidance

## MIL-STD-1760: Connection Interface (Functional)
Missile will be compatible to standard aircraft weapon connection interface

## MIL-STD-704: Electric Power Standard (Functional)
Missile will comply to military electric power standard

## MIL-STD-6016: Data Link System (Functional)
Missile will be compatible to link 16 data link system

## RFP: Cost (Functional)
Missile Cost will be less than $500,000

## MIL-STD-461: Electromagnetic Resistance (Functional)
Missile will be redundant to electromagnetic interference

## MIL-HDBK-781: Reliability (Functional)
Missile will meet military reliability requirement

## RCTA-DO-160: Aerial Durability (Functional)
Missile will have durability required to endure aerial environmental challenge

## MIL-STD-810: Ground Durability (Functional)
Missile will have durability required to endure ground environemntal challenge

## MIL-STD-882: Safety Req. (Functional)
Missile will meet military safety requirement

## Hunter_Dillon-STD: Bro (Functional)
I love Hunter Dillon <3.
